module ietf-empty {


    namespace "urn:opencord:params:xml:ns:voltha:ietf-empty";
    prefix empty;


    organization "CORD";
    contact
        " Any name";

    description
        "";

    revision "2016-11-15" {
        description "Initial revision.";
        reference "reference";
    }


    grouping Empty {
        description
            "A generic empty message that you can re-use to avoid defining duplicated
 empty messages in your APIs. A typical example is to use it as the request
 or the response type of an API method. For instance:

     service Foo  
       rpc Bar(google.protobuf.Empty) returns (google.protobuf.Empty);
      

 The JSON representation for `Empty` is empty JSON object `  `.";
    }

}
