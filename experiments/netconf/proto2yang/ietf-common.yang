module ietf-common {


    namespace "urn:opencord:params:xml:ns:voltha:ietf-common";
    prefix common;


    organization "CORD";
    contact
        " Any name";

    description
        "";

    revision "2016-11-15" {
        description "Initial revision.";
        reference "reference";
    }

    typedef LogLevel {
        type enumeration {
            enum DEBUG {
                description "";
            }
            enum INFO {
                description "";
            }
            enum WARNING {
                description "";
            }
            enum ERROR {
                description "";
            }
            enum CRITICAL {
                description "";
            }
        }
        description
            "Logging verbosity level";
    }
    typedef AdminState {
        type enumeration {
            enum AS_UNKNOWN {
                description "";
            }
            enum AS_PREPROVISIONED {
                description "";
            }
            enum AS_ENABLED {
                description "";
            }
            enum AS_DISABLED {
                description "";
            }
        }
        description
            "Administrative State";
    }
    typedef OperStatus {
        type enumeration {
            enum OS_UNKNOWN {
                description "";
            }
            enum OS_DISCOVERED {
                description "";
            }
            enum OS_ACTIVATING {
                description "";
            }
            enum OS_TESTING {
                description "";
            }
            enum OS_ACTIVE {
                description "";
            }
            enum OS_FAILED {
                description "";
            }
        }
        description
            "Operational Status";
    }
    typedef ConnectStatus {
        type enumeration {
            enum CS_UNKNOWN {
                description "";
            }
            enum CS_UNREACHABLE {
                description "";
            }
            enum CS_REACHABLE {
                description "";
            }
        }
        description
            "Connectivity Status";
    }

    grouping ID {
        description
            "Convey a resource identifier";
        leaf id {
            type  string; 
            description
                "";
        }

    }

}
