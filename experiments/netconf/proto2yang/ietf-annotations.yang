module ietf-annotations {


    namespace "urn:opencord:params:xml:ns:voltha:ietf-annotations";
    prefix annotations;


    organization "CORD";
    contact
        " Any name";

    description
        "";

    revision "2016-11-15" {
        description "Initial revision.";
        reference "reference";
    }


}
